(defun xzt (r0 a0 t0 tool_type /
               old_osmode old_cmdecho old_orthomode old_clayer old_attdia product_name material drawing_prefix)
  ;;===============????????????????????defun???????????????????????===============
  (vl-load-com)  ; ????ActiveX???
  ;; ????????????
  (setq old_osmode (getvar "osmode"))
  (setq old_cmdecho (getvar "cmdecho"))
  (setq old_orthomode (getvar "orthomode"))
  (setq old_clayer (getvar "clayer"))
  (setq old_attdia (getvar "attdia"))
  
  ;; ?????????????
  (defun *error* (msg)
    (if (/= msg "Function cancelled")
      (progn
        (princ "\n")
        (princ "??????: ")
        (princ msg)
      )
    )
    ;; ???????????
    (setvar "osmode" old_osmode)
    (setvar "cmdecho" old_cmdecho)
    (setvar "orthomode" old_orthomode)
    (setvar "clayer" old_clayer)
    (setvar "attdia" old_attdia)
    (setvar "dimtofl" 1)
    ;; ???????
    (princ)
  )
  
  ;; ?????????????
  (setvar "osmode" 16384)       ;?????
  (setvar "cmdecho" 0)      ;?????????????
  (setvar "orthomode" 0)    ;??????
  (setvar "attdia" 0)       ;????????????????????
  
  
  ;;=================??????????===================
  (if (null tool_type)
    (progn
      (initget 1 "1 2 3 4 5")
      (setq tool_type (getkword "\n??????????: 1. ??????????? 2. ?????????? 3. ??????????? 4. ?????????? 5. ??????????? "))
    )
  )
  
  ;; ?????????????¨°???
  (cond
    ((= tool_type "1")
     (setq product_name "???????????")
     (setq material "HT40-20")
     (setq drawing_prefix "GPMJX"))
    
    ((= tool_type "2")
     (setq product_name "??????????")
     (setq material "LY12")
     (setq drawing_prefix "GPMXJ"))
    
    ((= tool_type "3")
     (setq product_name "???????????")
     (setq material "HT40-20")
     (setq drawing_prefix "QX"))
    
    ((= tool_type "4")
     (setq product_name "??????????")
     (setq material "LY12")
     (setq drawing_prefix "QZ"))
    
    ((= tool_type "5")
     (setq product_name "???????????")
     (setq material "LY12")
     (setq drawing_prefix "QP"))
    
    (T
     (princ "\n?????§¹???????????")
     (exit))
  )
  ;;?????????????????????????
  (princ (strcat "\n=== " product_name " ==="))
  (princ (strcat "\n????: " material))
  (princ (strcat "\n?????: " drawing_prefix))
  
  ;;=================????????????¨²?????????????????=========================
  (princ "\n=== §³?????????????? ===")
  (if (null r0) (setq r0 (getdist "\n???????????: ")))
  (if (null a0) (setq a0 (getdist "\n????????(???): ")))
  (if (null t0) (setq t0 (getdist "\n????????: ")))
  
  ;; ?????????????????
  (if (or (null r0) (null a0) (null t0) (<= r0 0) (<= a0 0) (<= t0 0))
    (progn
      (princ "\n????: ????????????0?????????")
      ;; ???????????
      (setvar "osmode" old_osmode)
      (setvar "cmdecho" old_cmdecho)
      (setvar "orthomode" old_orthomode)
      (setvar "clayer" old_clayer)
      (setvar "attdia" old_attdia)
      (princ)
      (exit)
    )
  )
  
  ;; ???????????????????????
  (if (< (* 2 r0) a0)
    (progn
      (princ "\n???????§³??????????????????????????")
      ;; ???????????
      (setvar "osmode" old_osmode)
      (setvar "cmdecho" old_cmdecho)
      (setvar "orthomode" old_orthomode)
      (setvar "clayer" old_clayer)
      (setvar "attdia" old_attdia)
      (princ)
      (exit)
    )
  )
  
  ;; ??????????????????????/Rr0-??a0??
  (setq drawing_no (strcat drawing_prefix "/R-" 
                           (rtos r0 2 4)     ; ???????????????¦Ë§³??
                           "-??" 
                           (rtos a0 2 2)))   ; ?????????????¦Ë§³??
  
  ;; ?????????????
  (setq current_date (menucmd "M=$(edtime,$(getvar,date),YYYY/MO/DD)"))
  
  ;; ??????????????
  (princ (strcat "\n????????: " drawing_no))
  (princ (strcat "\n???????: " current_date))
  
 ;;================????????????========================
  (setq a1 (/ a0 2))                                ; ????
  (setq c_pt0 (list 0 0))                           ; ????????
  (setq sag (- r0 (sqrt (- (* r0 r0) (* a1 a1)))))  ; ??????
  (setq t_pt1 (list 0 (- (+ sag t0))))              ; ???????1????????y????
  (setq l_pt1 (list (- (- a1 0.5)) 0))              ; ??????1
  (setq r_pt1 (list (- a1 0.5) 0))                  ; ??????1
  (setq c_pt1 (list 0 -0.5))                        ; ?????????1
  (setq l_pt2 (list (- a1) -0.5))                   ; ??????2
  (setq r_pt2 (list a1 -0.5))                       ; ??????2
  (setq c_pt2 (list 0 (- t0)))                      ; ???????2??c_pt0?¡¤?t0????
  (setq l_pt3 (list (- a1) (- t0)))                 ; ????????3
  (setq r_pt3 (list a1 (- t0)))                     ; ????????3
  (setq q_pt1 (list 5 30))                          ; ??????????1
  (setq q_pt2 (list 5 0))                           ; ????????2
  (setq c_pt3 (list 0 (- (- (- sag) t0) 3)))        ; ???????3
  (setq c_pt4 (list 0 33))                          ; ???????4
  (setq h0 (- r0 sag))                              ; ??????????h0 = r0 - sag
  (setq c_pt5 (list 0 (+ (- t0) h0)))               ; ????5??????c_pt2???h0????
  
  ;; ????????????????????????????????????????
  (setq angL (angle c_pt5 l_pt3))                   ; ?????????????
  (setq angR (angle c_pt5 r_pt3))                   ; ?????????????
  (setq angB (angle c_pt5 t_pt1))                   ; ????????????????
  ;; ????????¦Ë???????????????
  (setq l_pt4 (polar c_pt5 (/ (+ angL angB) 2.0) r0))  ; ????????4
  ;; ????????¦Ë???????????????
  ;(setq r_pt4 (polar c_pt5 (/ (+ angR angB) 2.0) r0))  ; ????????4
  (setq ang1 (/ (+ angR angB) 2.0))
  (setq r_pt4(polar c_pt5 ang1 r0))
  
  ;; [????????????????????]
  (setq q_pt3 (list 1 (- t0)))                         ; ???????3
  (setq q_pt4 (list 11.5 8.25))                        ; ???????4

  
  ;;============???????=============
  ;; ?§Ý????????????
  (setvar "clayer" "??????")
  ;; ?????????????????
  (setq w1 (list -100 100)
	w2 (list 100 -100))
  (command "zoom" "w" w1 w2)
  ;; ?????"§³???¦Â"????????c_pt0
  (command "insert" "§³???¦Â" c_pt0 "1" "1" "0")
  
  ;; ????????c_pt0??l_pt1
  (command "line" c_pt0 l_pt1 "")  
  ;; ????????l_pt1??l_pt2
  (command "line" l_pt1 l_pt2 "")
  ;; ????????l_pt2??c_pt1
  (command "line" l_pt2 c_pt1 "")
  ;; ????????l_pt2??l_pt3
  (command "line" l_pt2 l_pt3 "")
  ;; ????????l_pt3??c_pt2
  (command "line" l_pt3 c_pt2 "")
  ;; ????????q_pt2??r_pt1
  (command "line" q_pt2 r_pt1 "")
  ;; ????????l\r_pt1??r_pt2
  (command "line" r_pt1 r_pt2 "")
  ;; ????????r_pt2??r_pt3
  (command "line" r_pt2 r_pt3 "")  
  ;; ????????????l_pt3?????r_pt3????r0
  (command "arc" l_pt3 "e" r_pt3 "r" r0)
  
  ;; ??????????
  ;; ?§Ý????????????
  (setvar "clayer" "??????")  
  ;; ????????c_pt3??c_pt4
  (command "line" c_pt3 c_pt4 "")

  
  ;;=============???===============
  ;; ?§Ý???????????
  (setvar "clayer" "?????")
  
  ;; 1. ???????????¦Ë????r_pt4?????¡¤????0.5??
  ;; ??????????
  (setq old_dimtofl (getvar "dimtofl"))
  (setvar "dimtofl" 0)
  ;;??????
  ;(setvar "osmode" 512)
  (setq dim_pt5 (list (+ (car r_pt4) 0.5) (- (cadr r_pt4) 0.5)))
  ;;?????????¦Ë??
  ;(command "line" r_pt4 dim_pt5 "")
  
  ;(command "dimradius" r_pt4 dim_pt5)
  (command "dimradius" r_pt4 "@0.5,-0.5")
  ;;???????
  ;(setvar "osmode" 0)
  ;; ???????????
  (setvar "dimtofl" old_dimtofl)
  (princ (strcat "\n=== ?????????? ==="))
  
  ;; 2. ???l_pt3??r_pt3??????????????? sag+18??
  (setq dim_dy1 (- 0 sag 18))
  (setq dim_pt1 (list 0 dim_dy1))
  (command "dimlinear" l_pt3 r_pt3 "h" "t" "%%c<>" dim_pt1)
  
  ;; 3. ???r_pt1??r_pt3???????????????5.5??
  (setq dim_pt2 (list (+ (car r_pt1) 5.5) (/ (+ (cadr r_pt1) (cadr r_pt3)) 2)))
  (command "dimlinear" r_pt1 r_pt3 "v" dim_pt2)
  
  ;; 4. ???q_pt1??r_pt1????????r_pt1???????21??
  (setq dim_pt3 (list (+ (car q_pt1) 21) (/ (+ (cadr q_pt1) (cadr r_pt1)) 2)))
  (command "dimlinear" q_pt1 r_pt1 "v" dim_pt3)
  
  ;; 5. ???q_pt1??t_pt1?????????§Ø?dim_pt2??dim_pt3???????????¦Ë?????????5.5??????????????????????????????
  (setq old_dimdec (getvar "dimdec"))
  (setvar "dimdec" 1)
  (setq dim_dx1 (car dim_pt2))
  (setq dim_dx2 (car dim_pt3))
  (if(> dim_dx1 dim_dx2)
    (setq dim_pt4 (list (+ dim_dx1 5.5) (/ (+ (cadr q_pt1) (cadr t_pt1)) 2)))
    (setq dim_pt4 (list (+ dim_dx2 5.5) (/ (+ (cadr q_pt1) (cadr t_pt1)) 2)))
  )
  (command "dimlinear" q_pt1 t_pt1 "v" "t" "(<>)" dim_pt4)
  (setvar "dimdec" old_dimdec)
  
  ;;=============??????===============
  ;; ?§Ý????????????
  (setvar "clayer" "??????")
  
  ;; ???ANSI31????????????q_pt3
  (command "-hatch" "p" "ANSI31" "1" "" q_pt3 "")
  
  ;; ?§Ý??????????
  (setvar "clayer" "?????")

  ;;==============??¦Ë???????›¨???????================
  ;; ????????????1????????????????3??????????????????????????
  (if (or (= tool_type "1") (= tool_type "3"))
    (progn
      ;???????????
      (command "insert" "????" l_pt4 "1" "1" "0")
    )
    ;; ??????????1??3???????????????
  )

  
  ;;==============?????????===========
  ;; ?????????????
  (command "zoom" "all")
  
  ;;============?§Ý?????????=============
  (setup_layout_and_titleblock)

  ;; ?????????????
  (command "zoom" "all")
  
  ;; ???????????
  (setvar "osmode" old_osmode)
  (setvar "cmdecho" old_cmdecho)
  (setvar "orthomode" old_orthomode)
  (setvar "clayer" old_clayer)
  (setvar "attdia" old_attdia)
  
  ;; ??????????
  (princ (strcat "\n=== " product_name " ???????? ==="))
  (princ (strcat "\n???: " drawing_no))
  (princ (strcat "\n????: " material))
  (princ)
)



;;???????§Ö???????

;;==========================================
;; ?????????????????
;;==========================================
(defun add_technical_requirements ()
  ;; ??????????
  (command "pspace")

  ;;????????????¨®¨À?Standard??
  (command "-style" "Standard" "" "" "" "" "" "")

  ;;????????¨®?????
  ;(setvar "clayer" "?????")

  ;; ????????????????????
  (setq text_corner1 '(-5 50))
  (setq text_corner2 '(45 0))

  ;; ????????????????????????
  (setq tech_text "")
  (if (or (= tool_type "1") (= tool_type "3"))
    ;; ????????1??3???????
    (setq tech_text "???????\n1.??????§Ù????????????\n2.????0.5*45??\n3.???????????V???????2??????2?? ?????\n4???????")
    ;; ????????2??4??5???????
    (setq tech_text "???????\n1.??????§Ù????????????\n2.????0.5*45??\n3.???????")
  )

  ;; ????????????
  (command "mtext" text_corner1 text_corner2 tech_text "")
)

;;==========================================
;; ???¨°?????????????????§Ó????ï‚
;;==========================================
(defun setup_layout_and_titleblock ()
  ;; ?§Ý????????
  (setvar "tilemode" 0)
  
  ;; ??ö÷??"A4??"??????
  (if (layout_exists "A4??")
    (progn
      ;; ?§Ý???"A4??"????
      (command "layout" "set" "A4??")
      
      ;; ????????§Ý????
      (while (> (getvar "CMDACTIVE") 0)
        (command "")
      )
      
      ;; ??öã????"A4???"??
      (if (tblsearch "BLOCK" "A4???")
        (progn
          ;; ???????÷Ï?????????1:1??
          (setq titleblock_origin '(0 0))
          (command "insert" "A4???" titleblock_origin "1" "1" "0")
          
          ;; ??????????
          (while (> (getvar "CMDACTIVE") 0)
            (command "")
          )
          
          ;; ????????????
          (set_attributes_of_titleblock)
        )
        (progn
          (princ "\n????: ¦Ä???'A4???'?ï…????????????")
        )
      )
      
      ;; ?????????????????1:1??
      (create_simple_viewport)
    )
    (progn
      (princ "\n????: ????'A4??'???????")
      ;; ???????????
      (setvar "tilemode" 1)
    )
  )
)

;;==========================================
;; ?????????????????1:1??
;;==========================================
(defun create_simple_viewport ()
  ;; ???????????????????1:1
  ;; ????????¦Ë?¨²??§³
  
  (setq vp_center (list 5 15))  ; A4??????
  (setq vp_width 250)  ; ??????
  (setq vp_height 180) ; ?????
  
  ;; ???????
  (command "mview" vp_center (list (+ (car vp_center) vp_width) 
                                   (+ (cadr vp_center) vp_height)))
  
  ;; ??????????
  (while (> (getvar "CMDACTIVE") 0)
    (command "")
  )
  ;; ??????????????????????
  (setq vp_ent (entlast))
  (command "change" vp_ent "" "p" "la" "???" "")
  
  ;; ????????????????
  (command "mspace")
  
  ;; ??????????
  (command "zoom" "c" '(0 0) "100")
  
  ;; ???????????1:1
  (command "zoom" "1xp")
  
  ;; ?????????
  (command "pspace")
  
  ;;??????????
  (add_technical_requirements)
)


;;==========================================
;; ????????????
;;==========================================
(defun set_attributes_of_titleblock ()
  ;; ????A4??????????

  ;; ??????????÷Ï???
  (setq block_ent (entlast))

  ;; ??????????
  (if (and block_ent 
           (= (cdr (assoc 0 (entget block_ent))) "INSERT")
           (= (cdr (assoc 2 (entget block_ent))) "A4???"))
    (progn
      ;; ???????????????ÈÉ?????????????
      (setq next_ent (entnext block_ent))
      (while next_ent
        (setq ent_data (entget next_ent))
        
        ;; ??????????????
        (if (= (cdr (assoc 0 ent_data)) "ATTRIB")
          (progn
            (setq tag_name (cdr (assoc 2 ent_data)))  ; ??????
            
            ;; ???????????????????
            (cond
              ((or (wcmatch tag_name "*????*") 
                   (wcmatch tag_name "*NAME*")
                   (wcmatch tag_name "*name*"))
               (entmod (subst (cons 1 product_name) (assoc 1 ent_data) ent_data)))
              
              ((or (wcmatch tag_name "*???*") 
                   (wcmatch tag_name "*NO*")
                   (wcmatch tag_name "*Drawing*"))
               (entmod (subst (cons 1 drawing_no) (assoc 1 ent_data) ent_data)))
              
              ((or (wcmatch tag_name "*????*") 
                   (wcmatch tag_name "*MATERIAL*")
                   (wcmatch tag_name "*material*"))
               (entmod (subst (cons 1 material) (assoc 1 ent_data) ent_data)))
              
              ((or (wcmatch tag_name "*????*") 
                   (wcmatch tag_name "*SCALE*")
                   (wcmatch tag_name "*scale*"))
               (entmod (subst (cons 1 "1:1") (assoc 1 ent_data) ent_data)))
              
              ((or (wcmatch tag_name "*????*") 
                   (wcmatch tag_name "*DATE*")
                   (wcmatch tag_name "*date*"))
               (entmod (subst (cons 1 current_date) (assoc 1 ent_data) ent_data)))
              
              ((or (wcmatch tag_name "*???????*") 
                   (wcmatch tag_name "*MODIFY*")
                   (wcmatch tag_name "*modify*"))
               (entmod (subst (cons 1 current_date) (assoc 1 ent_data) ent_data)))
               ;; ????¦Ä????????????????
              (T
               (princ (strcat "\n????????????: " tag_name))
               ;; ?????????????????
               )
            )
            
            ;; ???????????
            (entupd next_ent)
          )
        )
        
        (setq next_ent (entnext next_ent))
      )
      
      ;; ?????????
      (entupd block_ent)
      
      (princ "\n?????????????¨À?")
    )
    (princ "\n????: ¦Ä???A4?????ï…????????????")
  )
)

;;==========================================
;; ??ö÷????????
;;==========================================
(defun layout_exists (layout_name)
  (vl-load-com)
  (setq acad_doc (vla-get-activedocument (vlax-get-acad-object)))
  (setq exists nil)
  (vlax-for layout (vla-get-layouts acad_doc)
    (if (= (strcase (vla-get-name layout)) (strcase layout_name))
      (setq exists T)
    )
  )
  exists
)




(defun c:xzt () (xzt nil nil nil nil) (princ))
